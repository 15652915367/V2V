V2xBsmRequest DEFINITIONS AUTOMATIC TAGS ::= 
BEGIN 
	IMPORTS  TransmissionState,
	BrakePedalStatus,
	TractionControlStatus,
	AntiLockBrakeStatus,
	StabilityControlStatus,
	BrakeBoostApplied,
	AuxiliaryBrakeStatus,
	SpeedConfidence,
	HeadingConfidence,
	SteeringWheelAngleConfidence,
	PositionConfidence,
	ElevationConfidence, 
	TimeConfidence FROM Enumerateds			
	FLOAT, 
	DOUBLE,
	MsgCount,
	DYear,
	DMonth,
	DDay,
	DHour,
	DMinute,
	DSecond,
	DTimeOffset,
	BasicVehicleClass,
	Latitude,
	Longitude,
	Elevation,
	Acceleration,
	VerticalAcceleration,
	YawRate,
	TimeOffset,
	CoarseHeading,
	ResponsErrodCode,
	TIMESTAMP,
	Speed,
	Heading,
	SteeringWheelAngle, 	
	Confidence,
	PositionOffsetLLV,
	Position3D,
    ExteriorLights FROM Common; 
    
	--主要包体	    
    --	V2xBsmRequestBody ::= SEQUENCE {
    --		msgCnt MsgCount,
    --		vid OCTET STRING (SIZE(17)),
    --		timestamp TIMESTAMP,
    --		
    --		v2xBsmRequestList V2xBsmRequestList    	
    --	}
    --	V2xBsmRequestList ::=SEQUENCE(SIZE(1..10))OF V2xBsmRequestElement
    --	V2xBsmRequestElement ::= SEQUENCE{
    	V2VBsmJamMsg ::= SEQUENCE{
			msgCnt MsgCount,
			vid OCTET STRING (SIZE(17)),
			bsmOrJam BsmOrJam,
			jamLevel JamLevel OPTIONAL,

			timestamp TIMESTAMP,
			plateNo OCTET STRING (SIZE(16)) OPTIONAL,
			--Reserved for Electronic Vehicle Identification
			secMark DSecond,
			pos Position3D,
			accuracy PositionConfidenceSet,
			transmission TransmissionState,
			speed Speed,
			heading Heading,
			angle SteeringWheelAngle OPTIONAL,
			motionCfd MotionConfidenceSet OPTIONAL,
			accelSet AccelerationSet4Way,
			brakes BrakeSystemStatus,
			size VehicleSize,
			vehicleClass VehicleClassification,
			--VehicleClassification includes BasicVehicleClass and other extendible type
			safetyExt VehicleSafetyExtensions OPTIONAL        
		}

		--标识是Bsm包还是 Jam拥堵包
		BsmOrJam ::= ENUMERATED {
			bsm(0),--Bsm packet
			jam(1)--Jam packet
		}
		--若该包是 Jam拥堵包,该项才有效为预警等级
		JamLevel ::= INTEGER(0..5)

		
		--定义四轮的加速状态
		BrakeAppliedStatus ::= BIT STRING { unavailable(0), leftFront(1), leftRear(2), rightFront(3), rightRear(4) }
		
		--定义车辆历史轨迹 
		PathHistory ::= SEQUENCE {
			initialPosition FullPositionVector OPTIONAL,
			currGNSSstatus GNSSstatus OPTIONAL,
			crumbData PathHistoryPointList
		}
		
		--定义完整的参考轨迹点信息
		FullPositionVector ::= SEQUENCE {
			utcTime DDateTime OPTIONAL,--time with msec precision
			pos Position3D,
			heading Heading OPTIONAL,
			transmission TransmissionState OPTIONAL,
			speed Speed OPTIONAL,
			posAccuracy PositionConfidenceSet OPTIONAL,
			timeConfidence TimeConfidence OPTIONAL,
			posConfidence PositionConfidenceSet OPTIONAL,
			motionCfd MotionConfidenceSet OPTIONAL
		}
		
		--定义车辆的历史轨迹点
		PathHistoryPoint ::= SEQUENCE { 
			llvOffset PositionOffsetLLV,
			timeOffset TimeOffset,--Offset backwards in time 
			speed Speed OPTIONAL,--Speed over the reported period 
			posAccuracy PositionConfidenceSet OPTIONAL,--The accuracy of this value
			heading CoarseHeading OPTIONAL --overall headng
		}
		
		--定义完整的日期和时间数单元
		DDateTime ::= SEQUENCE{
			year DYear OPTIONAL,
			month DMonth OPTIONAL,
			day DDay OPTIONAL,
			hour DHour OPTIONAL,
			minute DMinute OPTIONAL,
			second DSecond OPTIONAL,
			offset DTimeOffset OPTIONAL --time zone
		}
		
		--定义GNSS系统工作状态
		GNSSstatus ::= BIT STRING {
			unavailable (0),--Not Equipped or unavai]ab]e 
			isHealthy (1),
			isMonitored (2),
			baseStationType (3),--Set to zero if a moving base station,
			--or if a rover device (an OBU),
			--set to one if it is a fixed base station 
			aPDOPofUnder5 (4),--A dilution of precision greater than 5
			inviewOfUnder5 (5),--Less than 5 satellites in view 
			localCorrectionsPresent (6),--DGPS type cotions used 
			networkCorrectionsPresent (7)--RTK type corrections used
			} (SIZE(8))
		
		--定义车辆历史轨迹
		PathHistoryPointList ::= SEQUENCE (SIZE(1.. 23)) OF PathHistoryPoint
		
		--定义车辆的分类 从各维度对车辆类型进行定义
		VehicleClassification ::= SEQUENCE {
			classification BasicVehicleClass
		}
	
		--PositionConfidenceSet	定义三维坐标位置的综合精度
		PositionConfidenceSet ::= SEQUENCE {
			pos PositionConfidence,
			--for both horizontal directions
			elevation ElevationConfidence OPTIONAL
		}		
	
		--	描述车辆运行状态的精度
		--包括车速精度、航向精度、方向盘转角精度
		MotionConfidenceSet ::= SEQUENCE {
			speedCfd SpeedConfidence OPTIONAL,
			headingCfd HeadingConfidence OPTIONAL,
			steerCfd SteeringWheelAngleConfidence OPTIONAL
		}
	    
		--定义车辆四轴加速度
		AccelerationSet4Way ::= SEQUENCE {
			long Acceleration,
			lat Acceleration,
			vert VerticalAcceleration,
			yaw YawRate
		}
	    
		--定义车辆的刹车系统状态
		BrakeSystemStatus ::= SEQUENCE {
			brakePadel BrakePedalStatus OPTIONAL,
			wheelBrakes BrakeAppliedStatus OPTIONAL,
			traction TractionControlStatus OPTIONAL,
			abs AntiLockBrakeStatus OPTIONAL,
			scs StabilityControlStatus OPTIONAL,
			brakeBoost BrakeBoostApplied OPTIONAL,
			auxBrakes AuxiliaryBrakeStatus OPTIONAL
		}
	    
		--	定义车辆尺寸大小
		VehicleSize ::= SEQUENCE {
			width VehicleWidth,
			length VehicleLength,
			height VehicleHeight OPTIONAL
		}
	
		VehicleWidth::=INTEGER(0..1023)
		--LSB units are 1 cm with a range of>10 meters
	
		VehicleLength::=INTEGER(0..4095)
		--LSB units of 1 cm with a range of>40 meters
	
		VehicleHeight::=INTEGER(0..127)
		--LSB units of 5 cm , range to 6.35 meters
	
		--	定义车辆安全辅助信息集合
		VehicleSafetyExtensions::=SEQUENCE{
			events VehicleEventFlags OPTIONAL,
			pathHistory PathHistory OPTIONAL,
			pathPrediction PathPrediction OPTIONAL,
			lights ExteriorLights OPTIONAL
		}
	    
		--	定义了一系列车辆的特殊状态
		VehicleEventFlags ::= BIT STRING{
			eventHazrdLights(0),
			eventStopLineViolation(1),--Intersection Violation
			eventABSactivated(2),
			eventTractionControlLoss(3),
			eventStabilityControlactivated(4),
			eventHazardousMaterials(5),
			eventReservedl(6),
			eventHardBraking(7),
			eventLinghtsChanged(8),
			enentWipersChanged(9),
			eventFlatTire(10),
			eventDisabledVehicle(11),--The DisabledVehicle DF may also be sent
			eventAirBagDeloyment(12)
		}
	    
		--定义车辆的预测路线，主要是曲率半径
		PathPrediction ::=SEQUENCE{
			radiusOfCurve RadiusOfCurvature,
			 --LSB units of 10cm
			 --straight path to use value of32767
			confidence Confidence
			 --LSB units of 0.5 percent
		}
		--表示车辆预测自身前方行驶轨迹的曲率半径
		RadiusOfCurvature ::= INTEGER(-32767..32767)    
END
