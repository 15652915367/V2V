SmartCanRequest
DEFINITIONS
AUTOMATIC TAGS ::=
BEGIN

IMPORTS
	MsgCount, TIMESTAMP
	FROM Common;
	
	SmartCanRequestBody ::= SEQUENCE {
		msgCnt MsgCount, 
		timestamp TIMESTAMP,
		vid OCTET STRING (SIZE(17)),
		isautoDrive BOOLEAN,	
		wipers  WiperList OPTIONAL, 
		lights LightList  OPTIONAL,
		runnings  RunningList  OPTIONAL,
		safetys  SafetyList  OPTIONAL,
		others OthersList OPTIONAL
	}
	 
	WiperList ::=SEQUENCE(SIZE(1..32))OF Wiper
	
	Wiper ::=SEQUENCE{
		msgCnt MsgCount, 
		timeStamp TIMESTAMP,
		frontWiperSwitch FRONTWIPERSWITCH,
		frontWiperIntermSwitch FRONTWIPERINTERMSWITCH,
		rearWiper REARWIPER,
		frontWashingSwitch FRONTWASHINGSWITCH
	}
	
	FRONTWIPERSWITCH ::= ENUMERATED { 
		off(0),
		auto(1),
		low(2),
		high(3),
		mist(4)
	}
	
	FRONTWIPERINTERMSWITCH ::=INTEGER(0..7)
		
	
	REARWIPER ::= ENUMERATED {
		notactive(0),
		active(1) 
	}
	FRONTWASHINGSWITCH ::= ENUMERATED {
		inactive(0),
		active(1)
	}
		
	/*FRONTWIPERSWITCH ::=INTEGER(0..7)
	REARWIPER ::=INTEGER(0..1)
	FRONTWIPERINTERMSWITCH ::=INTEGER(0..7)
	FRONTWASHINGSWITCH ::=INTEGER(0..1)*/
	
	LightList ::=SEQUENCE(SIZE(1..32))OF Light
	Light ::=SEQUENCE{
		msgCnt MsgCount, 
		timeStamp TIMESTAMP,
		turningLampSwitch TURNINGLAMPSWITCH, 
		exexteriorLampSwitch EXTERIORLAMPSWITCH, 
		foglampSwitch FOGLAMPSWITCH, 
		telltaleFrontFoglight TELLTALEFRONTFOGLIGHT, 
		telltaleRearFoglight TELLTALEREARFOGLIGHT,
		lowBeamIndicator LOWBEAMINDICATOR, 
		highBeamIndiator HIGHBEAMINDICATOR, 
		brakeLightRightActive BRAKELIGHTRIGHTACTIVE, 
		brakeLightLeftActive BRAKELIGHTLEFTACTIVE, 
		parkLightOnWarning PARKLIGHTONWARNING  
	}
	TURNINGLAMPSWITCH ::= ENUMERATED {
		inactive(0),
		turnleft(1),
		turnright(2),
		error(3)
	}
	EXTERIORLAMPSWITCH ::= ENUMERATED { 
		off(0),
		auto(1),
		park(2),
		lowbeam(3)
	}
	FOGLAMPSWITCH ::= ENUMERATED {
		inactive(0),
		rearfog(1),
		frontfog(2),
		bothactive(3)
	}
	TELLTALEFRONTFOGLIGHT ::= ENUMERATED {
		notactive(0),
		active(1)
	}
	TELLTALEREARFOGLIGHT ::= ENUMERATED {
		notactive(0),
		active(1)
	}
	LOWBEAMINDICATOR ::= ENUMERATED {
		off(0),
		on(1)
	}
	HIGHBEAMINDICATOR ::= ENUMERATED {
		off(0),
		on(1)
	}
	BRAKELIGHTRIGHTACTIVE ::= ENUMERATED {
		off(0),
		on(1)
	}
	BRAKELIGHTLEFTACTIVE ::= ENUMERATED {
		off(0),
		on(1)
	}
	PARKLIGHTONWARNING ::= ENUMERATED {
		inactive(0),
		active(1)
	}
	
	/*TURNING_LAMP_SWITCH ::=INTEGER(0..3),
	EXTERIOR_LAMP_SWITCH ::=INTEGER(0..3),
	FOG_LAMP_SWITCH ::=INTEGER(0..3),
	TELLTALE_FRONT_FOG_LIGHT ::=INTEGER(0..1),
	TELLTALE_REAR_FOG_LIGHT ::=INTEGER(0..1),
	LOW_BEAM_INDICATOR ::=INTEGER(0..1),
	HIGH_BEAM_INDICATOR ::=INTEGER(0..1),
	BRAKE_LIGHT_RIGHT_ACTIVE ::=INTEGER(0..1),
	BRAKE_LIGHT_LEFT_ACTIVE ::=INTEGER(0..1),
	PARK_LIGHT_ON_WARNING  ::=INTEGER(0..1)*/
	
	RunningList ::=SEQUENCE(SIZE(1..32))OF Running
	Running ::=SEQUENCE{
		msgCnt MsgCount, 
		timeStamp TIMESTAMP,
		bareakPadelSwtichSts BreakPadelSwtichSts,
	    battSoc REAL(0..100),
		
		vcu616DriveRange REAL(0..6553.5),
		oilLeft REAL(0..100),
		longitudinalAcceleration REAL(-25..25),
		longitudinalOffset REAL(-25..25),
		lateralAcceleration REAL(-25..25),
		lateralOffset REAL(-25..25),
		yawVelocity REAL(-2.5..2.5),
		yawVelocityOffset REAL(-1..1),
		steeringWheelRotationSpeed REAL(0..1016),
		steeringWheelAngle REAL(-780..780),
		
		
		validAcceleator VALIDACCELERATOR,
		acceleratorPos REAL(0..100),
		totalOdo TotalODO,
		validWheelSpeedFl VALIDWHEELSPEEDFL,
		wheelSpeedFl REAL(0..300),
		validWheelFr VALIDWHEELSPEEDFR,
		wheelSpeedFr REAL(0..300),
		validWheelSpeedRl VALIDWHEELSPEEDRL,
		wheelSpeedRl REAL(0..300),
		validWheelRr VALIDWHEELSPEEDRR,
		wheelSpeedRr REAL(0..300),
		validVehicleSpeed VALIDVEHICLESPEED,
		vehicleSpeed REAL(0..300),
		motoSpeed REAL(0..16383.5)
	}
	BreakPadelSwtichSts ::= ENUMERATED {
		brakepedalnotactive(0),
		brakepedalactive(1)
	}
	
		
	VALIDACCELERATOR ::= ENUMERATED {
			valueok(0),
			notused(1),
		
			valueunreliable(2)
	}
		
	TotalODO ::=INTEGER(0..16777215)
	VALIDWHEELSPEEDFL ::= ENUMERATED {
			valueok(0),
			valueunreliable(1)
	}
	
	VALIDWHEELSPEEDFR ::= ENUMERATED {
			valueok(0),
			valueunreliable(1)
	}
		
	VALIDWHEELSPEEDRL ::= ENUMERATED {
			valueok(0),
			valueunreliable(1)
	}
		
	VALIDWHEELSPEEDRR ::= ENUMERATED {
			valueok(0),
			valueunreliable(1)
	}
	
	VALIDVEHICLESPEED ::= ENUMERATED {
			valueok(0),
			notused(1),
		
			valueunreliable(2)
	}
		
	/*BreakPadelSwtichSts ::=INTEGER(0..1),
    BATT_SOC ::=Float(0..100%),
	
	VCU_616_DRIVE_RANGE ::=Float(0..6553.5),
	OilLeft ::=Float(0..100%),
	LONGITUDINAL_ACCELERATION ::=Float(-25..25),
	LONGITUDINAL_OFFSET ::=Float(-25..25),
	LATERAL_ACCELERATION ::=Float(-25..25),
	LATERAL_OFFSET::=Float(-25..25),
	YAW_VELOCITY ::=Float(-2.5..2.5),
	YAW_VELOCITY_OFFSET ::=Float(-0.5..0.5),
	STEERING_WHEEL_ROTATION_SPEED ::=Float(0..1016),
	STEERING_WHEEL_ANGLE ::=Float(-780..780),
	VALID_ACCELERATOR ::=INTEGER(0..3),
	ACCELERATOR_POS ::=Float(0..100),
	Total_ODO (BMS) ::=INTEGER(0..16777215),
	VALID_WHEEL_SPEED_FL ::=INTEGER(0..3),
	WHEEL_SPEED_FL ::=Float(0..300),
	VALID_WHEEL_SPEED_FR ::=INTEGER(0..3),
	WHEEL_SPEED_FR ::=Float(0..300),
	VALID_WHEEL_SPEED_RL ::=INTEGER(0..3),
	WHEEL_SPEED_RL ::=Float(0..300),
	VALID_WHEEL_SPEED_RR ::=INTEGER(0..3),
	WHEEL_SPEED_RR ::=Float(0..300),
	VALID_VEHICLE_SPEED ::=INTEGER(0..3),
	VEHICLE_SPEED ::=Float(0..300),
	MotoSpeed (MOT_SPD) ::=Float(0..16383.5)
		VALIDACCELERATOR ::=INTEGER(0..3)
		
		TotalODO ::=INTEGER(0..16777215)
		VALIDWHEELSPEEDFL ::=INTEGER(0..3)
	
		VALIDWHEELSPEEDFR ::=INTEGER(0..3)
		
		VALIDWHEELSPEEDRL ::=INTEGER(0..3)
		
		VALIDWHEELSPEEDRR ::=INTEGER(0..3)
	
		VALIDVEHICLESPEED ::=INTEGER(0..3)
		*/
	
	SafetyList ::=SEQUENCE(SIZE(1..32))OF Safety
	Safety ::=SEQUENCE{
		msgCnt MsgCount, 
		timeStamp TIMESTAMP,
		absOperating ABSOPERATING,
		espAebActive ESPAEBactive,
		espOperating ESPOPERATING,
		tcsOperating TCSOPERATING,
		epsSta EPSSTA,
		tcuTgsmode TCUTGSMode,
		tcuCurrentgearposition TCUCurrentGearPosition
	}
	ABSOPERATING ::= ENUMERATED {
			inactive(0),
			active(1)
	}
	ESPAEBactive ::= ENUMERATED {
			inactive(0),
			active(1)
	}
	ESPOPERATING ::= ENUMERATED {
			inactive(0),
			active(1)
	}
	TCSOPERATING ::= ENUMERATED {
		 	inactive(0),
			active(1)
	}
	EPSSTA ::= ENUMERATED {
		 readiness(0),
		 normal(1),
		 fault(2),
		 void(3)
	}
	TCUTGSMode ::= ENUMERATED {
		 normal(0),
		 winter(1),
		 performance(2),
		 econonmy(3), 
		 inalid(4)
	}
	TCUCurrentGearPosition ::=INTEGER(0..4) 
	 /*ABS_OPERATING ::=INTEGER(0..1),
		ESP_AEB_active ::=INTEGER(0..1),
		ESP_OPERATING ::=INTEGER(0..1),
		TCS_OPERATING ::=INTEGER(0..1),
		EPS_STA ::=INTEGER(0..3),
		TCU_TGSMode ::=INTEGER(0..4),
		TCU_CurrentGearPosition ::=INTEGER(0x0..0xF)*/
	OthersList ::=SEQUENCE(SIZE(1..32))OF Other
	Other ::=SEQUENCE{
		msgCnt MsgCount, 
		timeStamp TIMESTAMP,
		outsideTemp REAL(-40..70),
		handBrake HANDBRAKE,
		autoHorn AutoHorn
	}
	
	HANDBRAKE ::= ENUMERATED {
		off(0),
		on(1)
	}
	AutoHorn ::= ENUMERATED {
		off(0),
		on(1)
	}
	/*OUTside_TEMP ::=Float(-40..70),
	HAND_BRAKE ::=INTEGER(0..1),
	AutoHorn ::=INTEGER(0..1)*/
END
