V2xBsmResponse
--Bsm响应消息
DEFINITIONS AUTOMATIC TAGS ::= BEGIN

	IMPORTS  MsgCount,TIMESTAMP,ResponsErrodCode FROM Common; 
		--消息体
		V2xBsmResponseBody::=SEQUENCE{
			msgCnt MsgCount,
		    timestamp TIMESTAMP,
		    vid OCTET STRING (SIZE(17)),
		    msgStatus BOOLEAN,
		    errorCode ResponsErrodCode
		}
	
END
